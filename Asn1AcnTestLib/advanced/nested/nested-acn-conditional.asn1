-- Requirement 48: Conditional presence in nested ACN definitions
-- Tests conditional presence or parametrization constructs in nested structures

NestedAcnConditional DEFINITIONS ::= BEGIN

    ConditionalInner ::= SEQUENCE {
        hasExtension BOOLEAN,
        baseField INTEGER (0..255),
        extensionField INTEGER (0..65535) OPTIONAL
    }

    ConditionalOuter ::= SEQUENCE {
        control INTEGER (0..15),
        inner ConditionalInner,
        optionalData OCTET STRING (SIZE(16)) OPTIONAL
    }

    NestedConditional ::= SEQUENCE {
        flags SEQUENCE {
            enableData1 BOOLEAN,
            enableData2 BOOLEAN,
            enableData3 BOOLEAN
        },
        data1 OCTET STRING (SIZE(8)) OPTIONAL,
        data2 OCTET STRING (SIZE(16)) OPTIONAL,
        data3 INTEGER (0..65535) OPTIONAL
    }

    TestStruct ::= SEQUENCE {
        outer ConditionalOuter,
        nested NestedConditional
    }

END
